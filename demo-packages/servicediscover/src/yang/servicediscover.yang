module servicediscover {

  namespace "http://example.com/servicediscover";
  prefix servicediscover;

  import ietf-inet-types { prefix inet; }
  import tailf-common { prefix tailf; }
  import tailf-ncs { prefix ncs; }

  description
    "Bla bla...";

  revision 2016-01-01 {
    description
        "Initial revision.";
  }

  container servicediscover {
    tailf:action discover {
      tailf:actionpoint discover;
      input {
        leaf service-type {
          type enumeration {
            enum L2Vpn;
            enum L3Vpn;
            enum DNSSync;
            enum Pcrf;
            enum L2Fw;
            enum RSMAcl;
          }  
          
        }
        leaf discover-type{
          type enumeration {
            enum action;
            enum xlst;
            enum attrbutes;
          }  

        }
        leaf action-name {
          type string;
        }
        leaf device-name {
          type leafref {
            path "/ncs:devices/ncs:device/ncs:name" ;
          }
        }
        leaf location {
          type string;
        }
      }
      output {
        leaf message {
          type string;
        }
        leaf success {
          type boolean;
        }
      }
    }
  }
}
